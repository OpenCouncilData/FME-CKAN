FME workspace publisher.fmw

Parameters:
- FILE_TO_UPLOAD = \\cogg.local\fs\IT\Shared\Spatial Systems\Data\data.gov.au\trees\packager\package\geelong_trees_shp\geelong_trees_2015_06_04.shz   # What file do you want to upload?
- FILE_TYPE = SHP   # What extension are you updating?
- DATASET_NAME = geelong-trees   # The name of the dataset on data.gov.au
- AUTH_CODE = INSERT_YOUR_API_KEY   # API Key

Note: Matt Swards / City of Ballarat / v1
Note: 1. MAKE A PRIVATE PARAMETER WITH YOUR AUTHORISATION/API KEY. THIS CAN BE FOUND ON YOUR PROFILE FROM DATA.GOV.AU
Creator
    GEOMTYPE = Geometry Object
    NUM = 1
    CREATED -> AttributeCreator
AttributeCreator
    ATTR_LIST = file_to_upload,$(FILE_TO_UPLOAD),filetype_to_upload,$(FILE_TYPE),dataset_url,https://data.gov.au/api/rest/dataset/$(DATASET_NAME),quote_to_remove,"
    -> AttributeCreator_2
AttributeCreator_2
    ATTR_LIST = dataset_url,@ReplaceString(@Value(dataset_url),@Value(quote_to_remove),"")
    -> HTTPCaller
Note: Call the dataset you wish to update via request URL and / rename response body attribute to response / https://data.gov.au/api/rest/dataset/DATASET_URL
HTTPCaller
    TARGET_ATTR_ENCODING = auto-detect
    STATUS_CODE_ATTR = _http_status_code
    CONNECTION_TIMEOUT_LENGTH = 60
    ERROR_ATTR = _error
    TRANSFER_TIMEOUT_LENGTH = 90
    CUSTOM_HEADERS = Authorization;$(AUTH_CODE)
    TARGET_ATTR = response
    HTTP_METHOD = GET
    SAVE_FILE = Attribute
    FOLLOW_REDIRECTS = Yes
    VERIFY_SSL_CERTIFICATES = Yes
    USE_COOKIES = No
    RESPONSE_HEADER_LIST_ATTR = _headers
    TARGET_URL = @Value(dataset_url)
    -> JSONFlattener
Note: Flatten the response
JSONFlattener
    JSON_ATTR = response
    RECURSIVE = Yes
    -> AttributeExposer
Note: Expose attributes from the response including id, / format and response list eg: response{}
AttributeExposer
    ATTR_LIST = resources{},format,id
    -> AttributeRenamer
Note: Rename the id to groupid. We need to extract / each resource id and this will cause havoc otherwise
AttributeRenamer
    ATTR_LIST = id,groupid,id
    -> AttributeRemover
AttributeRemover
    LIST_ATTRS = _headers{} _headers{}.name _headers{}.value
    -> ListExploder_2
Note: Explode the resource list to / extract each resource
ListExploder_2
    ATTR_CONFLICT_RES = Use Original
    INDEX_ATTR = _element_index
    LIST_ATTR = resources{}
    ATTR_ACCUM_MODE = Merge Incoming List
    LIST_FOUND -> AttributeExposer_2
Note: any attributes you would like to update on the resource such as last-modified, description etc can be exposed here for editing then pushed to an attribute setter if needed
AttributeExposer_2
    ATTR_LIST = id,package_id,url,ckan_url
    -> TestFilter
TestFilter
    TEST_LIST:
      BOOL_OP,OR,COMPOSITE_TEST,<Unused>,TEST_CLAUSE,"TEST
      @UpperCase(@Value(format)) =
      @UpperCase(@Value(filetype_to_upload))",@Value(format) = @Value(filetype_to_upload)
    DEFAULT_VALUE = <UNFILTERED>
    @Value(format) = @Value(filetype_to_upload) -> TimeStamper_2
Note: TimeStamper for the last_modified date of the resource
TimeStamper_2
    TIME_ATTR = last_modified
    FMT = ISO Date (^Y-^m-^d)
    -> HTTPCaller_2__2
Note: URL / http://data.gov.au/api/3/action/resource_update / Method - POST / HEADERS / Authorization - your private parameter API KEY / BODY / Multipart/form data / UPLOAD / Required fields / id - the id of the resource which has been extracted earlier / upload - the file being upload. needs application/octet-stream as mime type / Optional / last_modified - the last modified date created with the time stamper / any other field you might wish to update such as description etc
HTTPCaller_2__2
    TARGET_ATTR_ENCODING = auto-detect
    STATUS_CODE_ATTR = _http_status_code
    CONNECTION_TIMEOUT_LENGTH = 60
    ERROR_ATTR = _error
    TRANSFER_TIMEOUT_LENGTH = 90
    CUSTOM_HEADERS = Authorization;$(AUTH_CODE)
    TARGET_ATTR = _response_body
    HTTP_METHOD = POST
    UPLOAD_TYPE = Multipart / Form Data
    MULTIPARTS = id StringUpload SOURCE_EXPRESSION;@Value(id);MIME_TYPE;text/plain;FME_CONTROLLER_QUERY_FILE;transformers\dependencies\http\StringUpload.fme upload FileUpload SOURCE_FILE;@Value(file_to_upload);MIME_TYPE;application/octet-stream;FME_CONTROLLER_QUERY_FILE;transformers\dependencies\http\FileUpload.fme last_modified StringUpload SOURCE_EXPRESSION;@Value(last_modified);MIME_TYPE;text/plain;FME_CONTROLLER_QUERY_FILE;transformers\dependencies\http\StringUpload.fme
    SAVE_FILE = Attribute
    FOLLOW_REDIRECTS = No
    VERIFY_SSL_CERTIFICATES = Yes
    USE_COOKIES = No
    RESPONSE_HEADER_LIST_ATTR = _headers
    TARGET_URL = http://data.gov.au/api/3/action/resource_update
    -> HTTPCaller_2__2_Output
    <Rejected> -> HTTPCaller_2__2_Output
HTTPCaller_2__2_Output: Logger
    MESSAGE = Feature is:
    MAXCOORDS = 20
    MAXFEATS = 20
